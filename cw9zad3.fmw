FME workspace cw9zad3.fmw

Parameters:
- SourceDataset_POSTGIS_RASTER =
- SourceDataset_POSTGIS_RASTER_6 =
- SourceDataset_POSTGIS_RASTER_7 =
- SourceDataset_POSTGIS_RASTER_8 =
- SourceDataset_POSTGIS_RASTER_9 =

Readers:
- POSTGIS_RASTER_1: POSTGIS_RASTER from $(SourceDataset_POSTGIS_RASTER) in LL-WGS84
- POSTGIS_RASTER_2: POSTGIS_RASTER from $(SourceDataset_POSTGIS_RASTER_9) in EPSG:4326
- POSTGIS_RASTER_3: POSTGIS_RASTER from $(SourceDataset_POSTGIS_RASTER_7) in EPSG:4326
- POSTGIS_RASTER_4: POSTGIS_RASTER from $(SourceDataset_POSTGIS_RASTER_6)
- POSTGIS_RASTER_5: POSTGIS_RASTER from $(SourceDataset_POSTGIS_RASTER_8)

Exports (reader POSTGIS_RASTER_4)
    attributes: _count int8, _value varchar(200), _clipped char(3)
SQLCreator
    DATASET = postgres
    FORMAT = POSTGIS_RASTER
    POSTGIS_RASTER_NAMED_CONNECTION = postgres
    POSTGIS_RASTER_QUERY_FEATURE_TYPES_FOR_MERGE_FILTERS = Yes
    POSTGIS_RASTER_READER_META_ATTRIBUTES = fme_basename
    POSTGIS_RASTER_READ_TIME_WITH_TIMEZONE = Yes
    POSTGIS_RASTER_SCHEMAS_FOR_TABLE_LISTING = public
    SQL_STATEMENT:
      CREATE TABLE public.union AS
      SELECT ST_Union(rast)FROM "public"."Exports"
union (reader POSTGIS_RASTER_5)
    -> Reprojector
Reprojector
    DEST = EPSG:4326
    INTERPOLATION_TYPE_NAME = Nearest Neighbor
    RASTER_CELL_SIZE = Preserve Cells
    RASTER_TOLERANCE = 0.0
